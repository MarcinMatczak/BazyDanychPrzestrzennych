FME workspace proj3.fmw

Parameters:
- SourceDataset_SHAPEFILE = ""C:\Users\MN\Documents\AGH - praca zdalna\Semestr 5\Bazy danych przestrzennych\FME\zad3\T2019_KAR_POI_TABLE.shp" "C:\Users\MN\Documents\AGH - praca zdalna\Semestr 5\Bazy danych przestrzennych\FME\zad3\T2019_KAR_STREET_NODE.shp" "C:\Users\MN\Documents\AGH - praca zdalna\Semestr 5\Bazy danych przestrzennych\FME\zad3\T2019_KAR_STREETS.shp""   # Source Esri Shapefile(s)
- SourceDataset_CSV2 = C:\Users\MN\Documents\AGH - praca zdalna\Semestr 5\Bazy danych przestrzennych\FME\zad3\punkty.csv.txt   # Source CSV (Comma Separated Value) File(s)
- DestDataset_GEOJSON = C:\Users\MN\Documents\AGH - praca zdalna\Semestr 5\Bazy danych przestrzennych\FME\zad3\pois_Cost_yes.json   # Destination GeoJSON File
- DestDataset_GEOJSON_5 = C:\Users\MN\Documents\AGH - praca zdalna\Semestr 5\Bazy danych przestrzennych\FME\zad3\pois_Cost_yes.json   # Destination GeoJSON File
- DestDataset_FILEGDB_4 = C:\Users\MN\Documents\AGH - praca zdalna\Semestr 5\Bazy danych przestrzennych\FME\zad3\nodes_Cost_yes   # File Geodatabase
- DestDataset_GEOJSON_4 = C:\Users\MN\Documents\AGH - praca zdalna\Semestr 5\Bazy danych przestrzennych\FME\zad3\pois_Cost_no.json   # Destination GeoJSON File
- DestDataset_FILEGDB = C:\Users\MN\Documents\AGH - praca zdalna\Semestr 5\Bazy danych przestrzennych\FME\zad3\nodes_Cost_no   # File Geodatabase

Readers:
- SHAPEFILE_1: SHAPEFILE from $(SourceDataset_SHAPEFILE) in LL-WGS84
- CSV2_1: CSV2 from $(SourceDataset_CSV2)

Writers:
- GEOJSON_1: GEOJSON to $(DestDataset_GEOJSON)
- GEOJSON_2: GEOJSON to $(DestDataset_GEOJSON_5)
- GEOJSON_3: GEOJSON to $(DestDataset_GEOJSON_4)
- FILEGDB_3: FILEGDB to $(DestDataset_FILEGDB_4)
- FILEGDB_1: FILEGDB to $(DestDataset_FILEGDB)

T2019_KAR_STREETS (reader SHAPEFILE_1)
    attributes: LINK_ID long, ST_NAME char(254), REF_IN_ID long, NREF_IN_ID long, FUNC_CLASS char(1), SPEED_CAT char(1), FR_SPEED_L long, TO_SPEED_L long, DIR_TRAVEL char(1)
    -> Reprojector_4
Reprojector_4
    DEST = DHDN.Berlin/Cassini
    INTERPOLATION_TYPE_NAME = Nearest Neighbor
    RASTER_CELL_SIZE = Preserve Cells
    RASTER_TOLERANCE = 0.0
    SOURCE = Read from feature
    REPROJECTED -> ShortestPathFinder [NETWORK]
    REPROJECTED -> Tester_F
Tester_F
    BOOL_OP = OR
    COMPOSITE_TEST = 1
    TEST_CLAUSE = TEST @Value(DIR_TRAVEL) = F
    TEST_MODE = TEST
    PASSED -> AttributeManager
    FAILED -> Tester_T
AttributeManager
    ATTR_TABLE:
      SET_TO ForwardCost = 1
      SET_TO ReverseCost = 9999
    -> ShortestPathFinder_2 [NETWORK]
Tester_T
    BOOL_OP = OR
    COMPOSITE_TEST = 1
    TEST_CLAUSE = TEST @Value(DIR_TRAVEL) = T
    TEST_MODE = TEST
    PASSED -> AttributeManager_2
    FAILED -> AttributeManager_3
AttributeManager_2
    ATTR_TABLE:
      SET_TO ForwardCost = 9999
      SET_TO ReverseCost = 1
    -> ShortestPathFinder_2 [NETWORK]
AttributeManager_3
    ATTR_TABLE:
      SET_TO ForwardCost = 1
      SET_TO ReverseCost = 1
    -> ShortestPathFinder_2 [NETWORK]
CSV (reader CSV2_1)
    attributes: x x_coordinate, y y_coordinate
    -> VertexCreator
VertexCreator
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = No
    LINE -> Reprojector
Reprojector
    DEST = DHDN.Berlin/Cassini
    INTERPOLATION_TYPE_NAME = Nearest Neighbor
    RASTER_CELL_SIZE = Preserve Cells
    RASTER_TOLERANCE = 0.0
    SOURCE = LL-WGS84
    REPROJECTED -> ShortestPathFinder [FROM-TO]
    REPROJECTED -> ShortestPathFinder_2 [FROM-TO]
ShortestPathFinder_2
    ALLOW_UTURNS = Yes
    REORDER_CHOICE = None
    SNAP_POINTS = Yes
    SNAP_TOLERANCE = 200
    WEIGHT_ATTR_1 = ForwardCost
    WEIGHT_ATTR_2 = ReverseCost
    WEIGHT_ATTR_CHOICE = By Two Attributes
    PATH -> Bufferer_2
    PATH -> SpatialFilter_4 [Filter]
    PATH -> LengthCalculator_2
Bufferer_2
    ANGLE = 22.5
    CAP_STYLE = Arc
    CORNER_STYLE = Arc
    MODE = AREA
    OFFSET = 5
    OFFSET_UNITS = METERS
    PRECISION = APPROX
    BUFFERED -> SpatialFilter [Filter]
LengthCalculator_2
    DIM = 2
    LEN_ATTR = _length
    MULT = 1
    -> T2019_KAR_STREET_NODE (writer FILEGDB_1)
ShortestPathFinder
    ALLOW_UTURNS = Yes
    REORDER_CHOICE = None
    SNAP_POINTS = Yes
    SNAP_TOLERANCE = 200
    WEIGHT_ATTR_CHOICE = By Length
    PATH -> Bufferer
    PATH -> SpatialFilter_3 [Filter]
    PATH -> LengthCalculator
Bufferer
    ANGLE = 22.5
    CAP_STYLE = Arc
    CORNER_STYLE = Arc
    MODE = AREA
    OFFSET = 5
    OFFSET_UNITS = METERS
    PRECISION = APPROX
    BUFFERED -> SpatialFilter_2 [Filter]
LengthCalculator
    DIM = 2
    LEN_ATTR = _length
    MULT = 1
    -> T2019_KAR_STREET_NODE (writer FILEGDB_3)
T2019_KAR_STREET_NODE (reader SHAPEFILE_1)
    attributes: NODE_ID long, LINK_ID long, POINT_NUM long, Z_LEVEL long, INTERSECT char(1), LAT double, LON double
    -> Reprojector_3
Reprojector_3
    DEST = DHDN.Berlin/Cassini
    INTERPOLATION_TYPE_NAME = Nearest Neighbor
    RASTER_CELL_SIZE = Preserve Cells
    RASTER_TOLERANCE = 0.0
    SOURCE = Read from feature
    REPROJECTED -> SpatialFilter_3 [Candidate]
    REPROJECTED -> SpatialFilter_4 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_STREET_NODE (writer FILEGDB_3)
    PASSED -> StatisticsCalculator_2
StatisticsCalculator_2
    CALCULATION_MODE = NUMERIC
    FEAT_STATS = NODE_ID,NUMERIC_MODE,,,COUNT,,,,,,,,,
    SUMMARY -> T2019_KAR_STREET_NODE (writer FILEGDB_3)
T2019_KAR_STREET_NODE (writer FILEGDB_3)
    attributes: NODE_ID int, LINK_ID int, POINT_NUM int, Z_LEVEL int, INTERSECT text(1), LAT double, LON double
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_STREET_NODE (writer FILEGDB_1)
    PASSED -> StatisticsCalculator
StatisticsCalculator
    CALCULATION_MODE = NUMERIC
    FEAT_STATS = NODE_ID,NUMERIC_MODE,,,COUNT,,,,,,,,,
    SUMMARY -> T2019_KAR_STREET_NODE (writer FILEGDB_1)
T2019_KAR_STREET_NODE (writer FILEGDB_1)
    attributes: NODE_ID int, LINK_ID int, POINT_NUM int, Z_LEVEL int, INTERSECT text(1), LAT double, LON double
T2019_KAR_POI_TABLE (reader SHAPEFILE_1)
    attributes: POI_ID long, LINK_ID long, TYPE char(250), POI_NAME char(250), ST_NAME char(250), LAT double, LON double
    -> Reprojector_2
Reprojector_2
    DEST = DHDN.Berlin/Cassini
    INTERPOLATION_TYPE_NAME = Nearest Neighbor
    RASTER_CELL_SIZE = Preserve Cells
    RASTER_TOLERANCE = 0.0
    SOURCE = Read from feature
    REPROJECTED -> SpatialFilter [Candidate]
    REPROJECTED -> SpatialFilter_2 [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_STREETS (writer GEOJSON_2)
T2019_KAR_STREETS (writer GEOJSON_2)
    attributes: x float, y float, _total_cost string, POI_ID int, LINK_ID int, TYPE string, POI_NAME string, ST_NAME string, LAT float, LON float, _predicate string
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_STREETS (writer GEOJSON_3)
T2019_KAR_STREETS (writer GEOJSON_3)
    attributes: x float, y float, _total_cost string, POI_ID int, LINK_ID int, TYPE string, POI_NAME string, ST_NAME string, LAT float, LON float, _predicate string
